Attribute VB_Name = "Module1"
Option Explicit

'----------------------------------------------------------------------
' type InfoVille = Structure enregistrement feuille excel "TOTAL"
Type InfoVille
    code_geo As String
    lib_geo As String
    actif_local As Double
    actif_ext As Double
    actif_Total As Double
    X_Longitude As Double
    Y_Latitude As Double
End Type

'----------------------------------------------------------------------
' type InfoFlux = Structure enregistrement feuille excel "Flux_Sup_100"
Type InfoFlux
    code_geo_ori As String
    lib_geo_ori As String
    code_geo_dest As String
    lib_geo_dest As String
    actif As Double
End Type

'----------------------------------------------------------------------
' Divers constantes pour manipulation des données
Public Const Ratio_Y = 1.36
Public Const Ratio_Actif = 500
Public Const Ratio_GPS = 400000
Public Const Ratio_Actif_Ext = 2
Public Const Trait_Plein = 1 ' 1 = trait Plein, 0 = Trait Large au départ et fin à l'arrivée

'----------------------------------------------------------------------
' tableau des données relu de la feuille excel TOTAL
Public villearray() As InfoVille

'----------------------------------------------------------------------
' tableau des données relu de la feuille excel TOTAL
Public fluxarray() As InfoFlux
'----------------------------------------------------------------------


'----------------------------------------------------------------------
' Programme principal
Sub Traitement_Ville_Cercle()
    Ouvrir_Excel_Total
    Dessin_Autocad_Cercle

End Sub

'----------------------------------------------------------------------
' Programme principal
Sub Traitement_Ville_Cube()
    Ouvrir_Excel_Total
    Dessin_Autocad_Cube

End Sub
'----------------------------------------------------------------------
' Programme principal
Private Sub Dessin_Autocad_Cube()

    Dim docMgr As AcadDocument
    Dim item As Variant
    Dim i As Integer
    Dim NomLieu As String
    Dim newBlock As AcadBlock
    Dim insertionPnt(0 To 2) As Double
    Dim circleObj As AcadCircle
    Dim radius As Double
    Dim plineObj As AcadLWPolyline
    Dim points(0 To 5) As Double
    Dim plineObj2 As AcadLWPolyline
    Dim basePoint(0 To 2) As Double
    Dim rotationAngle As Double
    Dim TextObj As AcadText
    Dim corner(0 To 2) As Double
    Dim height As Double
    Dim text As String
    Dim color As AcadAcCmColor
    Dim blockRefObj As AcadBlockReference
    Dim layerColl As AcadLayers
    Dim Mylayer As AcadLayer


    ' Activation du documents AutoCad
    Set docMgr = AutoCAD.ActiveDocument ' Application.Documents
    
    ' Create a dimension style named "Communes" in current drawing
    Set layerColl = docMgr.Layers
    If layerColl.Count > 1 Then
        On Error Resume Next
        layerColl.item("Communes").Delete
    End If
    Err.Clear
    ' Purge des elements inutiles
    ThisDrawing.PurgeAll
    
    Set Mylayer = layerColl.Add("Communes")
    layerColl.item("Communes").LayerOn = True
        
    ' Boucle sur le tableau des communes
    For i = 1 To UBound(villearray, 1)
        '------------------------------------------------------------
        ' divers initialisation
        NomLieu = villearray(i).code_geo & "-" & villearray(i).lib_geo
        radius = Sqr((villearray(i).actif_Total * Ratio_Actif) * 3.141592)
        '------------------------------------------------------------
        ' Creation d'un nouveau Block avec un point d'insertion
        insertionPnt(0) = 0
        insertionPnt(1) = 0
        insertionPnt(2) = 0
        ' Ajout du block dans la collection
        Set newBlock = ThisDrawing.Blocks.Add(insertionPnt, NomLieu)
        '------------------------------------------------------------
        ' Définition du Cube Actif Locaux
        Dim curves(0 To 3) As AcadEntity
        Dim centerPoint(0 To 2) As Double
        Dim centerPoint2(0 To 2) As Double
        Dim centerPoint3(0 To 2) As Double
        Dim centerPoint4(0 To 2) As Double
        centerPoint(0) = 0
        centerPoint(1) = 0
        centerPoint(2) = 0
        centerPoint2(0) = 2000
        centerPoint2(1) = 0
        centerPoint2(2) = 0
        centerPoint3(0) = 2000
        centerPoint3(1) = 2000
        centerPoint3(2) = 0
        centerPoint4(0) = 0
        centerPoint4(1) = 2000
        centerPoint4(2) = 0
        ' Define the line
        Set curves(0) = newBlock.AddLine(centerPoint, centerPoint2)
        Set curves(1) = newBlock.AddLine(curves(0).EndPoint, centerPoint3)
        Set curves(2) = newBlock.AddLine(curves(1).EndPoint, centerPoint4)
        Set curves(3) = newBlock.AddLine(curves(2).EndPoint, curves(0).StartPoint)
            
        ' Create the region
        Dim regionObj As Variant
        regionObj = newBlock.AddRegion(curves)
        
        ' Define the extrusion
        Dim height2 As Double
        Dim taperAngle As Double
        height2 = villearray(i).actif_local
        taperAngle = 0
        
        ' Create the solid
        Dim solidObj As Acad3DSolid
        Set solidObj = newBlock.AddExtrudedSolid(regionObj(0), height2, taperAngle)
        Set color = AcadApplication.GetInterfaceObject("AutoCAD.AcCmColor.20")
        color.SetRGB 255, 0, 255
        solidObj.TrueColor = color
        '------------------------------------------------------------
        ' Définition du Cube Actif Externe
        centerPoint(0) = 2000
        centerPoint(1) = 0
        centerPoint(2) = 0
        centerPoint2(0) = 4000
        centerPoint2(1) = 0
        centerPoint2(2) = 0
        centerPoint3(0) = 4000
        centerPoint3(1) = 2000
        centerPoint3(2) = 0
        centerPoint4(0) = 2000
        centerPoint4(1) = 2000
        centerPoint4(2) = 0
        ' Define the line
        Set curves(0) = newBlock.AddLine(centerPoint, centerPoint2)
        Set curves(1) = newBlock.AddLine(curves(0).EndPoint, centerPoint3)
        Set curves(2) = newBlock.AddLine(curves(1).EndPoint, centerPoint4)
        Set curves(3) = newBlock.AddLine(curves(2).EndPoint, curves(0).StartPoint)
            
        ' Create the region
        'Dim regionObj As Variant
        regionObj = newBlock.AddRegion(curves)
        
        ' Define the extrusion
        'Dim height2 As Double
        'Dim taperAngle As Double
        height2 = villearray(i).actif_ext
        taperAngle = 0
        
        ' Create the solid
        'Dim solidObj As Acad3DSolid
        Set solidObj = newBlock.AddExtrudedSolid(regionObj(0), height2, taperAngle)
        Set color = AcadApplication.GetInterfaceObject("AutoCAD.AcCmColor.20")
        color.SetRGB 255, 255, 0
        solidObj.TrueColor = color
        '------------------------------------------------------------
        ' Ajouter le nom de la commune (en dessous)
        corner(0) = 0
        corner(1) = 0 - (1.1 * radius)
        corner(2) = 0
        height = 0.7 * radius
        text = villearray(i).lib_geo
        ' Ajout dans le block
        Set TextObj = newBlock.AddText(text, corner, height)
        Set color = AcadApplication.GetInterfaceObject("AutoCAD.AcCmColor.20")
        color.SetRGB 0, 0, 255
        TextObj.TrueColor = color
        '------------------------------------------------------------
        ' Insertion final du block
        insertionPnt(0) = villearray(i).X_Longitude
        insertionPnt(1) = villearray(i).Y_Latitude
        insertionPnt(2) = 0
        Set blockRefObj = ThisDrawing.ModelSpace.InsertBlock(insertionPnt, NomLieu, 1#, 1#, 1#, 0)
        '------------------------------------------------------------
    Next i
    ThisDrawing.Activate
    ThisDrawing.Application.ZoomAll
    ' Change the viewing direction of the viewport
    Dim NewDirection(0 To 2) As Double
    NewDirection(0) = -1
    NewDirection(1) = -2
    NewDirection(2) = 1
    ThisDrawing.ActiveViewport.Direction = NewDirection
    ThisDrawing.ActiveViewport = ThisDrawing.ActiveViewport
    'MsgBox "Done"
End Sub

'----------------------------------------------------------------------
' Programme principal
Private Sub Dessin_Autocad_Cercle()

    Dim docMgr As AcadDocument
    Dim item As Variant
    Dim i As Integer
    Dim NomLieu As String
    Dim newBlock As AcadBlock
    Dim insertionPnt(0 To 2) As Double
    Dim circleObj As AcadCircle
    Dim radius As Double
    Dim plineObj As AcadLWPolyline
    Dim points(0 To 5) As Double
    Dim plineObj2 As AcadLWPolyline
    Dim basePoint(0 To 2) As Double
    Dim rotationAngle As Double
    Dim TextObj As AcadText
    Dim corner(0 To 2) As Double
    Dim height As Double
    Dim text As String
    Dim color As AcadAcCmColor
    Dim blockRefObj As AcadBlockReference
    Dim layerColl As AcadLayers
    Dim Mylayer As AcadLayer


    ' Activation du documents AutoCad
    Set docMgr = AutoCAD.ActiveDocument ' Application.Documents
    
    ' Create a dimension style named "Communes" in current drawing
    Set layerColl = docMgr.Layers
    If layerColl.Count > 1 Then
        On Error Resume Next
        layerColl.item("Communes").Delete
    End If
    Err.Clear
    ' Purge des elements inutiles
    ThisDrawing.PurgeAll
    
    Set Mylayer = layerColl.Add("Communes")
    layerColl.item("Communes").LayerOn = True
        
    ' Boucle sur le tableau des communes
    For i = 1 To UBound(villearray, 1)
        '------------------------------------------------------------
        ' divers initialisation
        NomLieu = villearray(i).code_geo & "-" & villearray(i).lib_geo
        'rayon = racine de surface * pi
        radius = Sqr((villearray(i).actif_Total * Ratio_Actif) * 3.141592)
        '------------------------------------------------------------
        ' Creation d'un nouveau Block avec un point d'insertion
        insertionPnt(0) = 0
        insertionPnt(1) = 0
        insertionPnt(2) = 0
        ' Ajout du block dans la collection
        Set newBlock = ThisDrawing.Blocks.Add(insertionPnt, NomLieu)
        '------------------------------------------------------------
        ' Définition du cercle représentant le nombre total d'actif
        ' Ajout du cercle dans le block
        Set circleObj = newBlock.AddCircle(insertionPnt, radius)
        Set color = AcadApplication.GetInterfaceObject("AutoCAD.AcCmColor.20")
        color.SetRGB 255, 0, 255
        circleObj.TrueColor = color
        '------------------------------------------------------------
        ' Définition du cercle représentant la ville
        ' Ajout du cercle dans le block
        Set circleObj = newBlock.AddCircle(insertionPnt, radius * 0.2)
        Set color = AcadApplication.GetInterfaceObject("AutoCAD.AcCmColor.20")
        color.SetRGB 255, 255, 255
        circleObj.TrueColor = color
        '------------------------------------------------------------
        ' Définition du premier trait de séparation dans le cercle
        ' Define the 2D polyline points
        points(0) = 0
        points(1) = 0
        points(2) = 0
        points(3) = radius
        points(4) = 0
        points(5) = 0
        ' Ajout dans le block
        Set plineObj = newBlock.AddLightWeightPolyline(points)
        Set color = AcadApplication.GetInterfaceObject("AutoCAD.AcCmColor.20")
        color.SetRGB 0, 255, 255
        plineObj.TrueColor = color
        '------------------------------------------------------------
        ' Définition du trait de séparation actif local et externe dans le cercle
        ' Define the 2D polyline points
        points(0) = 0
        points(1) = 0
        points(2) = 0
        points(3) = radius
        points(4) = 0
        points(5) = 0
        ' Ajout dans le block
        Set plineObj2 = newBlock.AddLightWeightPolyline(points)
        Set color = AcadApplication.GetInterfaceObject("AutoCAD.AcCmColor.20")
        color.SetRGB 255, 255, 0
        plineObj2.TrueColor = color
        ' Définition de la rotation de la seconde ligne
        basePoint(0) = 0
        basePoint(1) = 0
        basePoint(2) = 0
        rotationAngle = (((villearray(i).actif_ext / villearray(i).actif_Total) * 360) / 180) * 3.141159
        ' Rotate the polyline
        plineObj2.Rotate basePoint, rotationAngle
        '------------------------------------------------------------
        ' Ajouter le nom de la commune (au dessus)
        corner(0) = 0
        corner(1) = 1.1 * radius
        corner(2) = 0
        height = 0.7 * radius
        text = villearray(i).lib_geo
        ' Ajout dans le block
        Set TextObj = newBlock.AddText(text, corner, height)
        Set color = AcadApplication.GetInterfaceObject("AutoCAD.AcCmColor.20")
        color.SetRGB 0, 0, 255
        TextObj.TrueColor = color
        '------------------------------------------------------------
        ' Insertion final du block
        insertionPnt(0) = villearray(i).X_Longitude
        insertionPnt(1) = villearray(i).Y_Latitude
        insertionPnt(2) = 0
        Set blockRefObj = ThisDrawing.ModelSpace.InsertBlock(insertionPnt, NomLieu, 1#, 1#, 1#, 0)
        '------------------------------------------------------------
    Next i
    ThisDrawing.Activate
    ThisDrawing.Application.ZoomAll
    'MsgBox "Done"
End Sub




'----------------------------------------------------------------------
' Programme principal
' version d'essai
Private Sub Dessin_Autocad_0()

    Dim docMgr As AcadDocument
    Dim item As Variant
    Dim i As Integer
    Dim NomLieu As String
    Dim newBlock As AcadBlock
    Dim insertionPnt(0 To 2) As Double
    Dim circleObj As AcadCircle
    Dim radius As Double
    Dim plineObj As AcadLWPolyline
    Dim points(0 To 5) As Double
    Dim plineObj2 As AcadLWPolyline
    Dim basePoint(0 To 2) As Double
    Dim rotationAngle As Double
    Dim TextObj As AcadText
    Dim corner(0 To 2) As Double
    Dim height As Double
    Dim text As String
    Dim color As AcadAcCmColor
    Dim blockRefObj As AcadBlockReference
    Dim layerColl As AcadLayers
    Dim Mylayer As AcadLayer


    ' Activation du documents AutoCad
    Set docMgr = AutoCAD.ActiveDocument ' Application.Documents
    
    ' Create a dimension style named "Communes" in current drawing
    Set layerColl = docMgr.Layers
    If layerColl.Count > 1 Then
        On Error Resume Next
        layerColl.item("Communes").Delete
    End If
    Err.Clear
    ' Purge des elements inutiles
    ThisDrawing.PurgeAll
    
    Set Mylayer = layerColl.Add("Communes")
    layerColl.item("Communes").LayerOn = True
        
    ' Boucle sur le tableau des communes
    For i = 1 To UBound(villearray, 1)
        '------------------------------------------------------------
        ' divers initialisation
        NomLieu = villearray(i).code_geo & "-" & villearray(i).lib_geo
        '------------------------------------------------------------
        ' Creation d'un nouveau Block avec un point d'insertion
        insertionPnt(0) = 0
        insertionPnt(1) = 0
        insertionPnt(2) = 0
        ' Ajout du block dans la collection
        Set newBlock = ThisDrawing.Blocks.Add(insertionPnt, NomLieu)
        '------------------------------------------------------------
        ' Définition du cercle représentant le nombre total d'actif
        radius = villearray(i).actif_Total * Ratio_Actif
        ' Ajout du cercle dans le block
        Set circleObj = newBlock.AddCircle(insertionPnt, radius)
        Set color = AcadApplication.GetInterfaceObject("AutoCAD.AcCmColor.20")
        color.SetRGB 255, 0, 255
        circleObj.TrueColor = color
        '------------------------------------------------------------
        ' Définition du premier trait de séparation dans le cercle
        ' Define the 2D polyline points
        points(0) = 0
        points(1) = 0
        points(2) = 0
        points(3) = villearray(i).actif_Total * Ratio_Actif
        points(4) = 0
        points(5) = 0
        ' Ajout dans le block
        Set plineObj = newBlock.AddLightWeightPolyline(points)
        Set color = AcadApplication.GetInterfaceObject("AutoCAD.AcCmColor.20")
        color.SetRGB 0, 255, 255
        plineObj.TrueColor = color
        '------------------------------------------------------------
        ' Définition du trait de séparation actif local et externe dans le cercle
        ' Define the 2D polyline points
        points(0) = 0
        points(1) = 0
        points(2) = 0
        points(3) = villearray(i).actif_Total * Ratio_Actif
        points(4) = 0
        points(5) = 0
        ' Ajout dans le block
        Set plineObj2 = newBlock.AddLightWeightPolyline(points)
        Set color = AcadApplication.GetInterfaceObject("AutoCAD.AcCmColor.20")
        color.SetRGB 255, 255, 0
        plineObj2.TrueColor = color
        ' Définition de la rotation de la seconde ligne
        basePoint(0) = 0
        basePoint(1) = 0
        basePoint(2) = 0
        rotationAngle = (((villearray(i).actif_ext / villearray(i).actif_Total) * 360) / 180) * 3.141159
        ' Rotate the polyline
        plineObj2.Rotate basePoint, rotationAngle
        '------------------------------------------------------------
        ' Ajouter le nom de la commune
        corner(0) = 1.1 * villearray(i).actif_Total * Ratio_Actif
        corner(1) = 0
        corner(2) = 0
        height = 0.2 * villearray(i).actif_Total * Ratio_Actif
        text = villearray(i).lib_geo
        ' Ajout dans le block
        Set TextObj = newBlock.AddText(text, corner, height)
        Set color = AcadApplication.GetInterfaceObject("AutoCAD.AcCmColor.20")
        color.SetRGB 0, 0, 255
        TextObj.TrueColor = color
        '------------------------------------------------------------
        ' Insertion final du block
        insertionPnt(0) = villearray(i).X_Longitude
        insertionPnt(1) = villearray(i).Y_Latitude
        insertionPnt(2) = 0
        Set blockRefObj = ThisDrawing.ModelSpace.InsertBlock(insertionPnt, NomLieu, 1#, 1#, 1#, 0)
        '------------------------------------------------------------
    Next i
    ThisDrawing.Activate
    ThisDrawing.Application.ZoomAll
    'MsgBox "Done"
End Sub


'----------------------------------------------------------------------
' Ouverture du fichier Excel, et lecture de la feuille TOTAL
Private Sub Ouvrir_Excel_Total()
    Dim xlFileName As String
    Dim xlApp As Excel.Application
    Dim blnIsOK As Boolean
    Dim xlBook As Excel.Workbook
    Dim xlSheet As Excel.Worksheet
    Dim xlrange As Excel.Range
    'Dim cols As Long
    'Dim rows As Long
    Dim rangeValue As Variant
    Dim i As Integer

    '--------------------------------------------------------
    blnIsOK = IsExcelRunning()
    If blnIsOK Then
        Set xlApp = GetObject(, "Excel.Application")
    Else
        Set xlApp = CreateObject("Excel.Application")
        xlApp.Visible = True
        xlApp.UserControl = True
    End If
    '--------------------------------------------------------
    ' Feuille Excel
    xlFileName = "F:\Mémoire\07 Protocoles\Final\Import_qgis.xls"
    xlApp.Application.ScreenUpdating = False
    ' open file for read
    Set xlBook = xlApp.Workbooks.Open(xlFileName)
    Set xlSheet = xlBook.Worksheets("TOTAL") ' desired sheet name , same if use xlBook.Worksheets(1)
    xlSheet.Activate
    Set xlrange = xlSheet.Range("A2:G1270") ' range address we interested in xlrange.Select
    'cols = xlrange.Columns.Count
    'rows = xlrange.rows.Count
    rangeValue = xlrange.Value2
    ' clean up memory
    xlBook.Close False
    Set xlBook = Nothing
    xlApp.Quit
    Set xlApp = Nothing
    ' end of work with Excel,
    '--------------------------------------------------------
    ' Redimensionnement du tableau
    ReDim villearray(1 To UBound(rangeValue, 1))
    ' Lecture des elements et typage des données
    For i = LBound(rangeValue, 1) To UBound(rangeValue, 1)
        villearray(i).code_geo = rangeValue(i, 1) ' code geo
        villearray(i).lib_geo = rangeValue(i, 2)   ' lib geo
        villearray(i).actif_local = CDbl(rangeValue(i, 3))  ' actif local
        villearray(i).actif_ext = CDbl(rangeValue(i, 4)) ' actif ext
        villearray(i).actif_Total = CDbl(rangeValue(i, 5)) ' actif total
        villearray(i).X_Longitude = Ratio_GPS * CDbl("0" & Replace(rangeValue(i, 6), ".", ",")) ' X Longitude
        villearray(i).Y_Latitude = Ratio_GPS * Ratio_Y * CDbl("0" & Replace(rangeValue(i, 7), ".", ",")) ' Y Latitude
    Next i
    'MsgBox CStr(i) & " Communes chargées"
End Sub


'----------------------------------------------------------------------
' Ouverture du fichier Excel, et lecture de la feuille Flux
Private Sub Ouvrir_Excel_Flux()
    Dim xlFileName As String
    Dim xlApp As Excel.Application
    Dim blnIsOK As Boolean
    Dim xlBook As Excel.Workbook
    Dim xlSheet As Excel.Worksheet
    Dim xlrange As Excel.Range
    'Dim cols As Long
    'Dim rows As Long
    Dim rangeValue As Variant
    Dim i As Integer

    '--------------------------------------------------------
    blnIsOK = IsExcelRunning()
    If blnIsOK Then
        Set xlApp = GetObject(, "Excel.Application")
    Else
        Set xlApp = CreateObject("Excel.Application")
        xlApp.Visible = True
        xlApp.UserControl = True
    End If
    '--------------------------------------------------------
    ' Feuille Excel
    xlFileName = "F:\Mémoire\07 Protocoles\Final\Import_qgis.xls"
    xlApp.Application.ScreenUpdating = False
    ' open file for read
    Set xlBook = xlApp.Workbooks.Open(xlFileName)
    Set xlSheet = xlBook.Worksheets("Flux_Sup_100") ' desired sheet name , same if use xlBook.Worksheets(1)
    xlSheet.Activate
    Set xlrange = xlSheet.Range("A2:E443") ' range address we interested in xlrange.Select
    'cols = xlrange.Columns.Count
    'rows = xlrange.rows.Count
    rangeValue = xlrange.Value2
    ' clean up memory
    xlBook.Close False
    Set xlBook = Nothing
    xlApp.Quit
    Set xlApp = Nothing
    ' end of work with Excel,
    '--------------------------------------------------------
    ' Redimensionnement du tableau
    ReDim fluxarray(1 To UBound(rangeValue, 1))
    ' Lecture des elements et typage des données
    For i = LBound(rangeValue, 1) To UBound(rangeValue, 1)
        fluxarray(i).code_geo_ori = rangeValue(i, 1)
        fluxarray(i).lib_geo_ori = rangeValue(i, 2)
        fluxarray(i).code_geo_dest = rangeValue(i, 3)
        fluxarray(i).lib_geo_dest = rangeValue(i, 4)
        fluxarray(i).actif = CDbl(rangeValue(i, 5))
    Next i
    'MsgBox CStr(i) & " Communes chargées"
End Sub

'---------------------------------------------------------------'
' Test si Exel est ouvert
Private Function IsExcelRunning() As Boolean
    Dim xlApp As Excel.Application
    On Error Resume Next
    Set xlApp = GetObject(, "Excel.Application")
    IsExcelRunning = (Err.Number = 0)
    Set xlApp = Nothing
    Err.Clear
End Function


Sub trait_Clermont()
   ' ThisDrawing.Blocks.item("63113-Clermont-Ferrand").Origin
    Dim lineObj As AcadLine
    Dim MyinsertionPoint(0 To 2) As Double
    Dim i As Integer
    Dim j As Integer
    Dim k As Integer
    Dim currInsertionPoint As Variant
    Dim DestInsertionPoint As Variant
    Dim radius As Double
    Dim radiusClerm As Double
    Dim color As AcadAcCmColor
    Dim plineObj As AcadLWPolyline
    Dim points(0 To 3) As Double
    
    ' Chargement du tableau de Flux
    Ouvrir_Excel_Flux
    
    ' récupération du point d'insertion du block de Clermont-Ferrand
    currInsertionPoint = ThisDrawing.ModelSpace.Layout.Block.item(924).InsertionPoint
    
    ' Parcours du tableau des flux
    For i = LBound(fluxarray, 1) To UBound(fluxarray, 1)
        ' si les actif se rendent à Clermont
        If fluxarray(i).code_geo_dest = "63113" Then
            '
            ' recherche du block de la ville de départ
            For j = 1 To ThisDrawing.Blocks.Count - 4
                If ThisDrawing.ModelSpace.Layout.Block.item(j).Name = fluxarray(i).code_geo_ori & "-" & fluxarray(i).lib_geo_ori Then
                    ' dessin de la liaison ville vers clermont
                    'Set lineObj = ThisDrawing.ModelSpace.AddLine(currInsertionPoint, ThisDrawing.ModelSpace.Layout.Block.item(j).InsertionPoint)
                    DestInsertionPoint = ThisDrawing.ModelSpace.Layout.Block.item(j).InsertionPoint
                    
                    ' Define the 2D polyline points
                    points(0) = DestInsertionPoint(0)
                    points(1) = DestInsertionPoint(1)
   
                    points(2) = currInsertionPoint(0)
                    points(3) = currInsertionPoint(1)
                    
                    ' Create a lightweight Polyline object in model space
                    Set plineObj = ThisDrawing.ModelSpace.AddLightWeightPolyline(points)
                    If Trait_Plein = 1 Then
                        plineObj.SetWidth 0, fluxarray(i).actif * Ratio_Actif_Ext, fluxarray(i).actif * Ratio_Actif_Ext
                    Else
                        plineObj.SetWidth 0, fluxarray(i).actif * Ratio_Actif_Ext, 0
                    End If
                    Set color = AcadApplication.GetInterfaceObject("AutoCAD.AcCmColor.20")
                    color.SetRGB 255, 0, 0
                    plineObj.TrueColor = color

                    ' pour forcer la sortie de la boucle de lecture des blocks
                    j = ThisDrawing.Blocks.Count
                End If
            Next j
        End If
    Next i
    
End Sub

Sub trait_Toute_Ville()
    Dim lineObj As AcadLine
    Dim MyinsertionPoint(0 To 2) As Double
    Dim i As Integer
    Dim j As Integer
    Dim k As Integer
    Dim currInsertionPoint As Variant
    Dim DestInsertionPoint As Variant
    Dim radius As Double
    Dim radiusClerm As Double
    Dim color As AcadAcCmColor
    Dim plineObj As AcadLWPolyline
    Dim points(0 To 3) As Double
    
    ' Chargement du tableau de Flux
    Ouvrir_Excel_Flux

    ' Parcours du tableau des flux
    For i = LBound(fluxarray, 1) To UBound(fluxarray, 1)
            points(0) = 0
            points(1) = 0
            
            points(2) = 0
            points(3) = 0
            
            ' recherche du block de la ville de départ
            For j = 0 To ThisDrawing.Blocks.Count - 4
                If ThisDrawing.ModelSpace.Layout.Block.item(j).Name = (fluxarray(i).code_geo_ori & "-" & fluxarray(i).lib_geo_ori) Then
                    ' récupération du point d'insertion du block
                    currInsertionPoint = ThisDrawing.ModelSpace.Layout.Block.item(j).InsertionPoint
                    ' pour forcer la sortie de la boucle de lecture des blocks
                    j = ThisDrawing.Blocks.Count
                End If
            Next j
            ' recherche du block de la ville d'arrivée
            For j = 0 To ThisDrawing.Blocks.Count - 4
                If ThisDrawing.ModelSpace.Layout.Block.item(j).Name = (fluxarray(i).code_geo_dest & "-" & fluxarray(i).lib_geo_dest) Then
                    DestInsertionPoint = ThisDrawing.ModelSpace.Layout.Block.item(j).InsertionPoint
                    ' pour forcer la sortie de la boucle de lecture des blocks
                    j = ThisDrawing.Blocks.Count
                End If
            Next j
                    
            If Not (currInsertionPoint(0) = 0) And Not (currInsertionPoint(1) = 0) And Not (DestInsertionPoint(0) = 0) And Not (DestInsertionPoint(1) = 0) Then
                ' Define the 2D polyline points
                points(0) = currInsertionPoint(0)
                points(1) = currInsertionPoint(1)
                
                points(2) = DestInsertionPoint(0)
                points(3) = DestInsertionPoint(1)
    
                ' Create a lightweight Polyline object in model space
                Set plineObj = ThisDrawing.ModelSpace.AddLightWeightPolyline(points)
                If Trait_Plein = 1 Then
                    plineObj.SetWidth 0, fluxarray(i).actif * Ratio_Actif_Ext, fluxarray(i).actif * Ratio_Actif_Ext
                Else
                    plineObj.SetWidth 0, fluxarray(i).actif * Ratio_Actif_Ext, 0
                End If
                Set color = AcadApplication.GetInterfaceObject("AutoCAD.AcCmColor.20")
                color.SetRGB 0, 255, 0
                plineObj.TrueColor = color
            End If
    Next i
    
End Sub

Attribute VB_Name = "Module2"

Option Explicit

'---------------------------------------------------------------'
' Notes:
' 1. requires settings: Tools -> Options -> General tab -> Error trapping field -> check "Break on Unhandled errors"
' 2. requires reference to Microsoft Excel XX.0 Object Library
'---------------------------------------------------------------'
' written by Sccadmember
' Date: Aug/04/06
' http://discussion.autodesk.com/threa...hreadID=489202
' Just thought I would post this because I have been looking for a working VBA file open dialog box
' solution for awhile. 'I'm an old autolisped making the jump to VBA and I have seen And read
' various solutons for the equivalent getfiled 'autolisp function but I never had much luck with them.
' This one worked for me it uses the Win API to do the job.
'---------------------------------------------------------------'
Private Declare PtrSafe Function GetOpenFileName Lib "comdlg32.dll" Alias "GetOpenFileNameA" (pOpenfilename As OPENFILENAME) As Long

Private Type OPENFILENAME
    lStructSize As Long
    hWndOwner As Long
    hInstance As Long
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long
    lpfnHook As Long
    lpTemplateName As String
End Type

' type InfoVille = Structure enregistrement feuille excel "TOTAL"
Type InfoVille
    code_geo As String
    lib_geo As String
    actif_local As Double
    actif_ext As Double
    actif_Total As Double
    X_Longitude As Double
    Y_Latitude As Double
End Type

Public Const Ratio_Y = 1.36
Public Const Ratio_Actif = 2
Public Const Ratio_GPS = 500000



    
    
'---------------------------------------------------------------'
Public Function ShowOpen(Filter As String, InitialDir As String, DialogTitle As String) As String
    Dim OFName As OPENFILENAME
    'Set the structure size
    OFName.lStructSize = Len(OFName)
    'Set the owner window
    OFName.hWndOwner = 0
    'Set the filter
    OFName.lpstrFilter = Filter
    'Set the maximum number of chars
    OFName.nMaxFile = 255
    'Create a buffer
    OFName.lpstrFile = Space(254)
    'Create a buffer
    OFName.lpstrFileTitle = Space$(254)
    'Set the maximum number of chars
    OFName.nMaxFileTitle = 255
    'Set the initial directory
    OFName.lpstrInitialDir = InitialDir
    'Set the dialog title
    OFName.lpstrTitle = DialogTitle
    'no extra flags
    OFName.flags = 0
    'Show the 'Open File' dialog
    If GetOpenFileName(OFName) Then
        ShowOpen = Trim(OFName.lpstrFile)
    Else
        ShowOpen = ""
    End If
End Function

'---------------------------------------------------------------'
Function IsExcelRunning() As Boolean
    Dim xlApp As Excel.Application
    On Error Resume Next
    Set xlApp = GetObject(, "Excel.Application")
    IsExcelRunning = (Err.Number = 0)
    Set xlApp = Nothing
    Err.Clear
End Function

Private Sub CreateDxfDocuments()
    ' To read data from specific Excel range
    Dim xlApp As Excel.Application
    Dim blnIsOK As Boolean
    Dim xlBook As Excel.Workbook
    Dim xlSheet As Excel.Worksheet
    blnIsOK = IsExcelRunning()
    If blnIsOK Then
        Set xlApp = GetObject(, "Excel.Application")
    Else
        Set xlApp = CreateObject("Excel.Application")
        xlApp.Visible = True
        xlApp.UserControl = True
    End If
    Dim xlFileName As String
    Dim Filter As String
    Dim InitialDir As String
    Dim DialogTitle As String
    
    Filter = "Excel Files (*.xlsx)" + Chr$(0) + "*.xlsx" + Chr$(0) + "All Files (*.*)" + Chr$(0) + "*.*" + Chr$(0)
    InitialDir = ThisDrawing.GetVariable("dwgprefix")
    DialogTitle = "Open an Excel file"
    
  '  xlFileName = ShowOpen(Filter, InitialDir, DialogTitle)
  
    ' to avoid using code above try hard coded file path,
    ' set full path of your Excel file here:
    xlFileName = "C:\Temp\Import_qgis.xls"
    xlApp.Application.ScreenUpdating = False
    ' open file for read
    Set xlBook = xlApp.Workbooks.Open(xlFileName)
    Set xlSheet = xlBook.Worksheets("TOTAL") ' desired sheet name , same if use
    'xlBook.Worksheets (1)
    xlSheet.Activate
    
    Dim xlrange As Excel.Range
    Set xlrange = xlSheet.Range("A2:G1270") ' range address we interested in xlrange.Select
    Dim cols As Long
    Dim rows As Long
    cols = xlrange.Columns.Count
    rows = xlrange.rows.Count
    Dim rangeValue As Variant
    rangeValue = xlrange.Value2
    ' clean up memory
    xlBook.Close False
    Set xlBook = Nothing
    xlApp.Quit
    Set xlApp = Nothing
    'DoEvents
    
    ' end of work with Excel,
    ' go to Autocad then
    'MsgBox "Back to AutoCAD"
    ''--------------------------------------------------------
    'Dim dxfname As String
    'dxfname = "-Sample.dxf"
    Dim ptarray() As InfoVille
    ReDim ptarray(1 To UBound(rangeValue, 1))
    Dim i As Integer
    For i = LBound(rangeValue, 1) To UBound(rangeValue, 1)
        ptarray(i).code_geo = rangeValue(i, 1) ' code geo
        ptarray(i).lib_geo = rangeValue(i, 2)   ' lib geo
        ptarray(i).actif_local = CDbl(rangeValue(i, 3))  ' actif local
        ptarray(i).actif_ext = CDbl(rangeValue(i, 4)) ' actif ext
        ptarray(i).actif_Total = CDbl(rangeValue(i, 5)) ' actif total
        ptarray(i).X_Longitude = Ratio_GPS * CDbl("0" & Replace(rangeValue(i, 6), ".", ",")) ' X Longitude
        ptarray(i).Y_Latitude = Ratio_GPS * Ratio_Y * CDbl("0" & Replace(rangeValue(i, 7), ".", ",")) ' Y Latitude
    Next i
    
    Dim docMgr As AcadDocument
    Set docMgr = AutoCAD.ActiveDocument ' Application.Documents
    Dim item As Variant
    Dim num As Integer
    num = 1
    
    
    ThisDrawing.PurgeAll
        
    Dim NomLieu As String
                
    For i = 1 To UBound(ptarray, 1)
        Dim newBlock As AcadBlock
        Dim insertionPnt(0 To 2) As Double
        
        NomLieu = ptarray(i).code_geo & "-" & ptarray(i).lib_geo
    
        ' Define the insertion point for the new block
        insertionPnt(0) = 0
        insertionPnt(1) = 0
        insertionPnt(2) = 0
    
        ' Add the new block into the Blocks collection
        Set newBlock = ThisDrawing.Blocks.Add(insertionPnt, NomLieu)
        
        'newBlock.AddCircle 0, 0.0001
       ' ' Define a circle
        Dim circleObj As AcadCircle
       ' Dim center(0 To 2) As Double
        Dim radius As Double
       ' center(0) = item(1): center(1) = item(2): center(2) = item(3)
        radius = ptarray(i).actif_Total * Ratio_Actif
        
       ' ' Add the circle to model space without using the mspace variable
        Set circleObj = newBlock.AddCircle(insertionPnt, radius)
        
        ' Add first line diagram
        Dim plineObj As AcadLWPolyline
        Dim points(0 To 5) As Double
        
        ' Define the 2D polyline points
        points(0) = 0
        points(1) = 0
        points(2) = 0
        points(3) = ptarray(i).actif_Total * Ratio_Actif
        points(4) = 0
        points(5) = 0
        
        ' Create a light weight Polyline object in model space
        Set plineObj = newBlock.AddLightWeightPolyline(points)
        
        ' Add second line diagram
        Dim plineObj2 As AcadLWPolyline
        
        ' Define the 2D polyline points
        points(0) = 0
        points(1) = 0
        points(2) = 0
        points(3) = ptarray(i).actif_Total * Ratio_Actif
        points(4) = 0
        points(5) = 0
         
        ' Create a light weight Polyline object in model space
        Set plineObj2 = newBlock.AddLightWeightPolyline(points)
        
       ' Define the rotation
        Dim basePoint(0 To 2) As Double
        Dim rotationAngle As Double
        basePoint(0) = 0
        basePoint(1) = 0
        basePoint(2) = 0
        rotationAngle = (((ptarray(i).actif_ext / ptarray(i).actif_Total) * 360) / 180) * 3.141159
        ' Rotate the polyline
        plineObj2.Rotate basePoint, rotationAngle
        
        
        Dim TextObj As AcadText
        Dim corner(0 To 2) As Double
        Dim height As Double
        Dim text As String
        corner(0) = 1.1 * ptarray(i).actif_Total * Ratio_Actif
        corner(1) = 0
        corner(2) = 0
        height = 0.2 * ptarray(i).actif_Total * Ratio_Actif
        text = ptarray(i).lib_geo
        
        ' Creates the mtext Object
        Set TextObj = newBlock.AddText(text, corner, height)
        Dim color As AcadAcCmColor
    Set color = AcadApplication.GetInterfaceObject("AutoCAD.AcCmColor.20")
    color.SetRGB 80, 100, 244
        TextObj.TrueColor = color
        
                        
                
        ' Insert the block
        Dim blockRefObj As AcadBlockReference
        insertionPnt(0) = ptarray(i).X_Longitude
        insertionPnt(1) = ptarray(i).Y_Latitude
        insertionPnt(2) = 0
        Set blockRefObj = ThisDrawing.ModelSpace.InsertBlock(insertionPnt, NomLieu, 1#, 1#, 1#, 0)
        
            
            
        num = num + 1
    Next i
    ThisDrawing.Application.ZoomAll
    'MsgBox "Done"
    
End Sub
'---------------------------------------------------------------'


Private Sub Example_AddExtrudedSolid()
    ' This example extrudes a solid from a region.
    ' The region is created from an arc and a line.
    
    Dim curves(0 To 3) As AcadEntity

    ' Define the arc
    Dim centerPoint(0 To 2) As Double
    Dim centerPoint2(0 To 2) As Double
    Dim centerPoint3(0 To 2) As Double
    Dim centerPoint4(0 To 2) As Double
    Dim radius As Double
    Dim startAngle As Double
    Dim endAngle As Double
    centerPoint(0) = 5
    centerPoint(1) = 3
    centerPoint(2) = 0
    centerPoint2(0) = 10
    centerPoint2(1) = 3
    centerPoint2(2) = 0
    centerPoint3(0) = 5
    centerPoint3(1) = 8
    centerPoint3(2) = 0
    centerPoint4(0) = 10
    centerPoint4(1) = 8
    centerPoint4(2) = 0
    radius = 2
    startAngle = 0
    endAngle = 3.141592
    
    ' Define the line
    Set curves(0) = ThisDrawing.ModelSpace.AddLine(centerPoint, centerPoint2)
    Set curves(1) = ThisDrawing.ModelSpace.AddLine(curves(0).EndPoint, centerPoint4)
    Set curves(2) = ThisDrawing.ModelSpace.AddLine(curves(1).EndPoint, centerPoint3)
    Set curves(3) = ThisDrawing.ModelSpace.AddLine(curves(2).EndPoint, curves(0).StartPoint)
        
    ' Create the region
    Dim regionObj As Variant
    regionObj = ThisDrawing.ModelSpace.AddRegion(curves)
    
    ' Define the extrusion
    Dim height As Double
    Dim taperAngle As Double
    height = 10
    taperAngle = 0
    
    ' Create the solid
    Dim solidObj As Acad3DSolid
    Set solidObj = ThisDrawing.ModelSpace.AddExtrudedSolid(regionObj(0), height, taperAngle)
    
    ' Change the viewing direction of the viewport
    Dim NewDirection(0 To 2) As Double
    NewDirection(0) = -1
    NewDirection(1) = -2
    NewDirection(2) = 1
    ThisDrawing.ActiveViewport.Direction = NewDirection
    ThisDrawing.ActiveViewport = ThisDrawing.ActiveViewport
    ZoomAll
        
End Sub
